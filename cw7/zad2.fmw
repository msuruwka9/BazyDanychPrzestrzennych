FME workspace zad2.fmw

Parameters:
- SourceDataset_TIFF = ""C:\Users\msuro\Desktop\Studia\S7\Bazy Danych Przestrzennych\ras250_gb\data\HP.tif" "C:\Users\msuro\Desktop\Studia\S7\Bazy Danych Przestrzennych\ras250_gb\data\HT.tif" "C:\Users\msuro\Desktop\Studia\S7\Bazy Danych Przestrzennych\ras250_gb\data\HU.tif" "C:\Users\msuro\Desktop\Studia\S7\Bazy Danych Przestrzennych\ras250_gb\data\HW.tif" "C:\Users\msuro\Desktop\Studia\S7\Bazy Danych Przestrzennych\ras250_gb\data\HX.tif" "C:\Users\msuro\Desktop\Studia\S7\Bazy Danych Przestrzennych\ras250_gb\data\HY.tif" "C:\Users\msuro\Desktop\Studia\S7\Bazy Danych Przestrzennych\ras250_gb\data\HZ.tif" "C:\Users\msuro\Desktop\Studia\S7\Bazy Danych Przestrzennych\ras250_gb\data\NA.tif" "C:\Users\msuro\Desktop\Studia\S7\Bazy Danych Przestrzennych\ras250_gb\data\NB.tif" "C:\Users\msuro\Desktop\Studia\S7\Bazy Danych Przestrzennych\ras250_gb\data\NC.tif" "C:\Users\msuro\Desktop\Studia\S7\Bazy Danych Przestrzennych\ras250_gb\data\ND.tif" "C:\Users\msuro\Desktop\Studia\S7\Bazy Danych Przestrzennych\ras250_gb\data\NF.tif" "C:\Users\msuro\Desktop\Studia\S7\Bazy Danych Przestrzennych\ras250_gb\data\NG.tif" "C:\Users\msuro\Desktop\Studia\S7\Bazy Danych Przestrzennych\ras250_gb\data\NH.tif" "C:\Users\msuro\Desktop\Studia\S7\Bazy Danych Przestrzennych\ras250_gb\data\NJ.tif" "C:\Users\msuro\Desktop\Studia\S7\Bazy Danych Przestrzennych\ras250_gb\data\NK.tif" "C:\Users\msuro\Desktop\Studia\S7\Bazy Danych Przestrzennych\ras250_gb\data\NL.tif" "C:\Users\msuro\Desktop\Studia\S7\Bazy Danych Przestrzennych\ras250_gb\data\NM.tif" "C:\Users\msuro\Desktop\Studia\S7\Bazy Danych Przestrzennych\ras250_gb\data\NN.tif" "C:\Users\msuro\Desktop\Studia\S7\Bazy Danych Przestrzennych\ras250_gb\data\NO.tif" "C:\Users\msuro\Desktop\Studia\S7\Bazy Danych Przestrzennych\ras250_gb\data\NR.tif" "C:\Users\msuro\Desktop\Studia\S7\Bazy Danych Przestrzennych\ras250_gb\data\NS.tif" "C:\Users\msuro\Desktop\Studia\S7\Bazy Danych Przestrzennych\ras250_gb\data\NT.tif" "C:\Users\msuro\Desktop\Studia\S7\Bazy Danych Przestrzennych\ras250_gb\data\NU.tif" "C:\Users\msuro\Desktop\Studia\S7\Bazy Danych Przestrzennych\ras250_gb\data\NW.tif" "C:\Users\msuro\Desktop\Studia\S7\Bazy Danych Przestrzennych\ras250_gb\data\NX.tif" "C:\Users\msuro\Desktop\Studia\S7\Bazy Danych Przestrzennych\ras250_gb\data\NY.tif" "C:\Users\msuro\Desktop\Studia\S7\Bazy Danych Przestrzennych\ras250_gb\data\NZ.tif" "C:\Users\msuro\Desktop\Studia\S7\Bazy Danych Przestrzennych\ras250_gb\data\OV.tif" "C:\Users\msuro\Desktop\Studia\S7\Bazy Danych Przestrzennych\ras250_gb\data\SC.tif" "C:\Users\msuro\Desktop\Studia\S7\Bazy Danych Przestrzennych\ras250_gb\data\SD.tif" "C:\Users\msuro\Desktop\Studia\S7\Bazy Danych Przestrzennych\ras250_gb\data\SE.tif" "C:\Users\msuro\Desktop\Studia\S7\Bazy Danych Przestrzennych\ras250_gb\data\SH.tif" "C:\Users\msuro\Desktop\Studia\S7\Bazy Danych Przestrzennych\ras250_gb\data\SJ.tif" "C:\Users\msuro\Desktop\Studia\S7\Bazy Danych Przestrzennych\ras250_gb\data\SK.tif" "C:\Users\msuro\Desktop\Studia\S7\Bazy Danych Przestrzennych\ras250_gb\data\SM.tif" "C:\Users\msuro\Desktop\Studia\S7\Bazy Danych Przestrzennych\ras250_gb\data\SN.tif" "C:\Users\msuro\Desktop\Studia\S7\Bazy Danych Przestrzennych\ras250_gb\data\SO.tif" "C:\Users\msuro\Desktop\Studia\S7\Bazy Danych Przestrzennych\ras250_gb\data\SP.tif" "C:\Users\msuro\Desktop\Studia\S7\Bazy Danych Przestrzennych\ras250_gb\data\SR.tif" "C:\Users\msuro\Desktop\Studia\S7\Bazy Danych Przestrzennych\ras250_gb\data\SS.tif" "C:\Users\msuro\Desktop\Studia\S7\Bazy Danych Przestrzennych\ras250_gb\data\ST.tif" "C:\Users\msuro\Desktop\Studia\S7\Bazy Danych Przestrzennych\ras250_gb\data\SU.tif" "C:\Users\msuro\Desktop\Studia\S7\Bazy Danych Przestrzennych\ras250_gb\data\SV.tif" "C:\Users\msuro\Desktop\Studia\S7\Bazy Danych Przestrzennych\ras250_gb\data\SW.tif" "C:\Users\msuro\Desktop\Studia\S7\Bazy Danych Przestrzennych\ras250_gb\data\SX.tif" "C:\Users\msuro\Desktop\Studia\S7\Bazy Danych Przestrzennych\ras250_gb\data\SY.tif" "C:\Users\msuro\Desktop\Studia\S7\Bazy Danych Przestrzennych\ras250_gb\data\SZ.tif" "C:\Users\msuro\Desktop\Studia\S7\Bazy Danych Przestrzennych\ras250_gb\data\TA.tif" "C:\Users\msuro\Desktop\Studia\S7\Bazy Danych Przestrzennych\ras250_gb\data\TF.tif" "C:\Users\msuro\Desktop\Studia\S7\Bazy Danych Przestrzennych\ras250_gb\data\TG.tif" "C:\Users\msuro\Desktop\Studia\S7\Bazy Danych Przestrzennych\ras250_gb\data\TL.tif" "C:\Users\msuro\Desktop\Studia\S7\Bazy Danych Przestrzennych\ras250_gb\data\TM.tif" "C:\Users\msuro\Desktop\Studia\S7\Bazy Danych Przestrzennych\ras250_gb\data\TQ.tif" "C:\Users\msuro\Desktop\Studia\S7\Bazy Danych Przestrzennych\ras250_gb\data\TR.tif" "C:\Users\msuro\Desktop\Studia\S7\Bazy Danych Przestrzennych\ras250_gb\data\TV.tif""   # Source TIFF (Tagged Image File Format) File(s)
- DestDataset_FILEGDB =   # File Geodatabase

Readers:
- TIFF_1: TIFF from $(SourceDataset_TIFF)

Writers:
- FILEGDB_1: FILEGDB to $(DestDataset_FILEGDB)

TIFF (reader TIFF_1)
    -> Reprojector
Reprojector
    DEST = LL-WGS84
    INTERPOLATION_TYPE_NAME = Nearest Neighbor
    RASTER_CELL_SIZE = Preserve Cells
    RASTER_TOLERANCE = 0.0
    REPROJECTED -> RasterPropertyExtractor
RasterPropertyExtractor
    -> AttributeCreator
AttributeCreator
    ATTR_TABLE = SET_TO path (varchar(200)) = C:\Users\msuro\Desktop\Studia\S7\Bazy Danych Przestrzennych\@Value(fme_basename)
    -> FilePropertyExtractor
FilePropertyExtractor
    FMT = FME Date/Time (%Y%m%d%H%M%S)
    PATH = @Value(path)
    -> AttributeCreator_2
    <Rejected> -> AttributeCreator_2
AttributeCreator_2
    ATTR_TABLE = SET_TO NewName (varchar(200)) = @Value(fme_basename)_@Value(_file_size)
    -> TIFF (writer FILEGDB_1)
TIFF (writer FILEGDB_1)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
